SUPL-POS DEFINITIONS AUTOMATIC TAGS ::= 
BEGIN 
 
EXPORTS SUPLPOS; 
 
IMPORTS Velocity 
  FROM ULP-Components; 
 
SUPLPOS ::= SEQUENCE { 
  posPayLoad  PosPayLoad, 
  velocity    Velocity OPTIONAL, 
  ...} 
 
PosPayLoad ::= CHOICE { 
  tia801payload  OCTET STRING(SIZE (1..8192)), 
  rrcPayload     OCTET STRING(SIZE (1..8192)), 
  rrlpPayload    OCTET STRING(SIZE (1..8192)), 
  ...} 
 
END
