JETDIRECT3-MIB DEFINITIONS ::= BEGIN

IMPORTS
     private, enterprises, Counter, Gauge, TimeTicks, NetworkAddress
          FROM RFC1065-SMI;


hp                  OBJECT IDENTIFIER ::= { enterprises 11 }
nm                  OBJECT IDENTIFIER ::= { hp 2 }
system              OBJECT IDENTIFIER ::= { nm 3 }
interface           OBJECT IDENTIFIER ::= { nm 4 }
snmp                OBJECT IDENTIFIER ::= { nm 13 }
net-peripheral      OBJECT IDENTIFIER ::= { system 9 }
net-printer         OBJECT IDENTIFIER ::= { net-peripheral 1 }
generalDeviceStatus OBJECT IDENTIFIER ::= { net-printer 1 }
ieee8023Mac         OBJECT IDENTIFIER ::= { interface 1 }
npCard              OBJECT IDENTIFIER ::= { interface 3 }
trap                OBJECT IDENTIFIER ::= { snmp 1 }
npSys               OBJECT IDENTIFIER ::= { npCard 1 }
npConns             OBJECT IDENTIFIER ::= { npCard 4 }
npCfg               OBJECT IDENTIFIER ::= { npCard 5 }
npTcp               OBJECT IDENTIFIER ::= { npCard 6 }
npCtl               OBJECT IDENTIFIER ::= { npCard 7 }
npNpi               OBJECT IDENTIFIER ::= { npCard 8 }
npElt               OBJECT IDENTIFIER ::= { npCard 9 }
npIpx               OBJECT IDENTIFIER ::= { npCard 10 }
llcconstategroup    OBJECT IDENTIFIER ::= { npCard 12 }


-- object types

-- The Status Group

gdStatusBytes OBJECT-TYPE
    SYNTAX  INTEGER
    ACCESS  read-only
    STATUS  optional
    DESCRIPTION
        "The number of valid bytes in the gdStatusEntry
         array."
    ::={ generalDeviceStatus 1 }

gdStatusEntry OBJECT-TYPE
    SYNTAX  GdStatusEntry
    ACCESS  not-accessible
    STATUS  optional
    DESCRIPTION
        "The networked peripheral's 32 octet status
         information that is shared between the peripheral
         and the LAN card."
    ::={ generalDeviceStatus 2 }

GdStatusEntry ::=
    SEQUENCE {
        gdStatusLineState
            INTEGER,
        gdStatusPaperState
            INTEGER,
        gdStatusInterventionState
            INTEGER,
        gdStatusNewMode
            INTEGER,
        gdStatusConnectionTerminationAck
            INTEGER,
        gdStatusPeripheralError
            INTEGER,
        gdStatusPaperOut
            INTEGER,
        gdStatusPaperJam
            INTEGER,
        gdStatusTonerLow
            INTEGER,
        gdStatusPagePunt
            INTEGER,
        gdStatusMemoryOut
            INTEGER,
        gdStatusIoActive
            INTEGER,
        gdStatusBusy
            INTEGER,
        gdStatusWait
            INTEGER,
        gdStatusInitialize
            INTEGER,
        gdStatusDoorOpen
            INTEGER,
        gdStatusPrinting
            INTEGER,
        gdStatusPaperOutput
            INTEGER,
        gdStatusReserved
            OCTET STRING,
        gdStatusNovBusy
            INTEGER,
        gdStatusLlcBusy
            INTEGER,
        gdStatusTcpBusy
            INTEGER,
        gdStatusAtBusy
            INTEGER
}

gdStatusLineState OBJECT-TYPE
    SYNTAX  INTEGER (0..255)
    ACCESS  read-only
    STATUS  optional
    DESCRIPTION
        "This describes the line state of the peripheral.
         When non-zero, the peripheral is off-line.  When
         zero the peripheral is on-line."
    ::={ gdStatusEntry 1 }

gdStatusPaperState OBJECT-TYPE
    SYNTAX  INTEGER (0..255)
    ACCESS  read-only
    STATUS  optional
    DESCRIPTION
        "This describes the state of the paper on the peripheral.
         When non-zero, the peripheral has a paper problem. When
         zero, the peripheral does not have a paper problem."
    ::={ gdStatusEntry 2 }

gdStatusInterventionState OBJECT-TYPE
    SYNTAX  INTEGER (0..255)
    ACCESS  read-only
    STATUS  optional
    DESCRIPTION
        "This describes the intervention state of the
         peripheral.  When non-zero, the peripheral requires
         human intervention to continue working.  When
         zero, it requires no assistance."
    ::={ gdStatusEntry 3 }

gdStatusNewMode OBJECT-TYPE
    SYNTAX  INTEGER (0..255)
    ACCESS  read-only
    STATUS  optional
    DESCRIPTION
        "This indicates to which read channel state the
         card should move.  When non-zero, the card should
         indicate that the read channel is idle.  When zero,
         the card should indicate that the read channel is
         operating.  This object is Lan Manager io channel 
         specific.  It is kept here for backward compatibility."
    ::={ gdStatusEntry 4 }

gdStatusConnectionTerminationAck OBJECT-TYPE
    SYNTAX  INTEGER (0..255)
    ACCESS  read-only
    STATUS  optional
    DESCRIPTION
        "This indicates whether the peripheral is waiting for
         the Connection termination ACK.  When non-zero, it
         is waiting.  When zero, it is not waiting."
    ::={ gdStatusEntry 5 }

gdStatusPeripheralError OBJECT-TYPE
    SYNTAX  INTEGER (0..255)
    ACCESS  read-only
    STATUS  optional
    DESCRIPTION
        "This is the error code from the peripheral."
    ::={ gdStatusEntry 6 }

gdStatusPaperOut OBJECT-TYPE
    SYNTAX  INTEGER 
--                OFF(0),
--                PAPER-OUT-OR-PAPER-MOUNT(1),
--                MANUAL-PAPER-FEED-NEEDED(2)
    ACCESS  read-only
    STATUS  optional
    DESCRIPTION
        "This indicates that the peripheral is out of paper.

         For some peripherals, such as the HP LaserJet IIISi printer
         or HP DesignJet plotter, this value is always a zero (0)."
    ::={ gdStatusEntry 8 }

gdStatusPaperJam OBJECT-TYPE
    SYNTAX  INTEGER 
--              OFF(0),
--              PAPER-JAM(1)
    ACCESS  read-only
    STATUS  optional
    DESCRIPTION
        "This indicates that the peripheral has a paper jam.
         For some peripherals, such as the HP LaserJet IIISi printer
         or HP DesignJet plotter, this value is always a zero (0)."
    ::={ gdStatusEntry 9 }

gdStatusTonerLow OBJECT-TYPE
    SYNTAX  INTEGER 
--              OFF(0),
--              TONER-LOW(1),
--              NO-TONER-CARTRIDGE(2)
    ACCESS  read-only
    STATUS  optional
    DESCRIPTION
        "This indicates that the peripheral has a low toner condition.
         For some peripherals, such as the HP LaserJet IIISi printer
         or HP DesignJet plotter, this value is always a zero (0)."
    ::={ gdStatusEntry 10 }

gdStatusPagePunt OBJECT-TYPE
    SYNTAX  INTEGER (0..255)
    ACCESS  read-only
    STATUS  optional
    DESCRIPTION
        "This indicates that the peripheral did not receive data fast
         enough to keep up with the print engine when generating a page.
         For some peripherals, such as the HP LaserJet IIISi printer
         or HP DesignJet plotter, this value is always a zero (0)."
    ::={ gdStatusEntry 11 }

gdStatusMemoryOut OBJECT-TYPE
    SYNTAX  INTEGER (0..255)
    ACCESS  read-only
    STATUS  optional
    DESCRIPTION
        "This indicates that the peripheral did not have enough memory
         to render an image on a page.
         For some peripherals, such as the HP LaserJet IIISi printer
         or HP DesignJet plotter, this value is always a zero (0)."
    ::={ gdStatusEntry 12 }

gdStatusIoActive OBJECT-TYPE
    SYNTAX  INTEGER (0..255)
    ACCESS  read-only
    STATUS  optional
    DESCRIPTION
        "This indicates that the peripheral is processing data from
         this I/O interface card.
         For some peripherals, such as the HP LaserJet IIISi printer
         or HP DesignJet plotter, this value is always a zero (0)."
    ::={ gdStatusEntry 13 }

gdStatusBusy OBJECT-TYPE
    SYNTAX  INTEGER (0..255)
    ACCESS  read-only
    STATUS  optional
    DESCRIPTION
        "This indicates that the peripheral is busy processing
         print/plot data.
         For some peripherals, such as the HP LaserJet IIISi printer
         or HP DesignJet plotter, this value is always a zero (0)."
    ::={ gdStatusEntry 14 }

gdStatusWait OBJECT-TYPE
    SYNTAX  INTEGER (0..255)
    ACCESS  read-only
    STATUS  optional
    DESCRIPTION
        "This indicates that the peripheral is waiting for print/plot
         data to process.
         For some peripherals, such as the HP LaserJet IIISi printer
         or HP DesignJet plotter, this value is always a zero (0)."
    ::={ gdStatusEntry 15 }

gdStatusInitialize OBJECT-TYPE
    SYNTAX  INTEGER 
--              OFF(0),
--              INITIALIZING(1),
--              WARM-UP(2)
    ACCESS  read-only
    STATUS  optional
    DESCRIPTION
        "This indicates that the peripheral is initializing or
         warming up.
         For some peripherals, such as the HP LaserJet IIISi printer
         or HP DesignJet plotter, this value is always a zero (0)."
    ::={ gdStatusEntry 16 }

gdStatusDoorOpen OBJECT-TYPE
    SYNTAX  INTEGER (0..255)
    ACCESS  read-only
    STATUS  optional
    DESCRIPTION
        "This indicates that the peripheral cover or door is open.
         For some peripherals, such as the HP LaserJet IIISi printer
         or HP DesignJet plotter, this value is always a zero (0)."
    ::={ gdStatusEntry 17 }

gdStatusPrinting OBJECT-TYPE
    SYNTAX  INTEGER 
--              OFF(0),
--              ORDINARY-PAGE(1),
--              TEST-FONTS-CONFIG-OR-START-PAGE(2)
    ACCESS  read-only
    STATUS  optional
    DESCRIPTION
        "This indicates that the peripheral is printing or otherwise
         marking or moving paper.
         For some peripherals, such as the HP LaserJet IIISi printer
         or HP DesignJet plotter, this value is always a zero (0)."
    ::={ gdStatusEntry 18 }

gdStatusPaperOutput OBJECT-TYPE
    SYNTAX  INTEGER 
--              OFF(0),
--              OUTPUT-STORAGE-FULL(1)
    ACCESS  read-only
    STATUS  optional
    DESCRIPTION
        "This indicates that the peripheral has a paper output problem
         such as the output storage bin being full.
         For some peripherals, such as the HP LaserJet IIISi printer
         or HP DesignJet plotter, this value is always a zero (0)."
    ::={ gdStatusEntry 19 }

gdStatusReserved OBJECT-TYPE
    SYNTAX  OCTET STRING (SIZE (0..13))
    ACCESS  read-only
    STATUS  optional
    DESCRIPTION
        "This is the reserved area that is not currently
         used, but will allow for growth within the gdStatusEntry table."
    ::={ gdStatusEntry 20 }

gdStatusNovBusy OBJECT-TYPE
    SYNTAX  INTEGER (0..255)
    ACCESS  read-only
    STATUS  optional
    DESCRIPTION
        "This indicates if this channel is active.  If the 
         value is 0 then this channel is active or the peripheral
         is idle.  If this value is non-zero then another channel
         is active.  This is the Novell io channel"
    ::={ gdStatusEntry 21 }

gdStatusLlcBusy OBJECT-TYPE
    SYNTAX  INTEGER (0..255)
    ACCESS  read-only
    STATUS  optional
    DESCRIPTION
        "This indicates if this channel is active.  If the 
         value is 0 then this channel is active or the peripheral
         is idle.  If this value is non-zero then another channel
         is active.  This is the LLC io channel"
    ::={ gdStatusEntry 22 }

gdStatusTcpBusy OBJECT-TYPE
    SYNTAX  INTEGER (0..255)
    ACCESS  read-only
    STATUS  optional
    DESCRIPTION
        "This indicates if this channel is active.  If the 
         value is 0 then this channel is active or the peripheral
         is idle.  If this value is non-zero then another channel
         is active.  This is the TCP io channel"
    ::={ gdStatusEntry 23 }

gdStatusAtBusy OBJECT-TYPE
    SYNTAX  INTEGER (0..255)
    ACCESS  read-only
    STATUS  optional
    DESCRIPTION
        "This indicates if this channel is active.  If the 
         value is 0 then this channel is active or the peripheral
         is idle.  If this value is non-zero then another channel
         is active.  This is the Apple talk io channel"
    ::={ gdStatusEntry 24 }

gdStatusDisplay OBJECT-TYPE
    SYNTAX  DisplayString (SIZE (0..255))
    ACCESS  read-only
    STATUS  optional
    DESCRIPTION
        "The string diplayed on the peripheral front panel.
         For some peripherals, such as the HP LaserJet IIISi printer
         or HP DesignJet plotter, this is always a zero length string."
    ::={ generalDeviceStatus 3 }

gdStatusJobName OBJECT-TYPE
    SYNTAX  DisplayString (SIZE (0..255))
    ACCESS  read-only
    STATUS  optional
    DESCRIPTION
        "The current job name set by the peripheral.
         For some peripherals, such as the HP LaserJet IIISi printer
         or HP DesignJet plotter, this is always a zero length string."
    ::={ generalDeviceStatus 4 }

gdStatusSource OBJECT-TYPE
    SYNTAX  DisplayString (SIZE (0..255))
    ACCESS  read-only
    STATUS  optional
    DESCRIPTION
        "A string indicating the name of the physical port or protocol
         the printer is currently getting data from."
    ::={ generalDeviceStatus 5 }

gdStatusPapstatus OBJECT-TYPE
    SYNTAX  DisplayString (SIZE (0..255))
    ACCESS  read-only
    STATUS  optional
    DESCRIPTION
        "A string indicating the Appletalk papstatus response."
    ::={ generalDeviceStatus 6 }

gdStatusId OBJECT-TYPE
    SYNTAX  DisplayString (SIZE (0..255))
    ACCESS  read-only
    STATUS  optional
    DESCRIPTION
        "A formatted string describing this peripheral."
    ::={ generalDeviceStatus 7 }

gdStatusDisplayCode OBJECT-TYPE
    SYNTAX  INTEGER 
    ACCESS  read-only
    STATUS  optional
    DESCRIPTION
        "This is the display code that the peripheral uses
         to tell the card what type of display the front
         panel of the printer is."
    ::={ generalDeviceStatus 8 }

gdStatusNlsCode OBJECT-TYPE
    SYNTAX  INTEGER
    ACCESS  read-only
    STATUS  optional
    DESCRIPTION
        "This value is the representation of what native
         language the printer is in currently."
    ::={ generalDeviceStatus 9 }

-- the Ieee8023Mac group

ieee8023MacTable OBJECT-TYPE
    SYNTAX  SEQUENCE OF Ieee8023MacEntry
    ACCESS  not-accessible
    STATUS  mandatory
    DESCRIPTION
        "A list of ieee8023MacEntry entries."
    ::= { ieee8023Mac 1 }

ieee8023MacEntry OBJECT-TYPE
    SYNTAX  Ieee8023MacEntry
    ACCESS  not-accessible
    STATUS  mandatory
    DESCRIPTION
        "An entry containing the hp ieee8023 extentions."
    INDEX   { ieee8023MacIndex }
    ::= { ieee8023MacTable 1 }

Ieee8023MacEntry ::= SEQUENCE {
    ieee8023MacIndex
        INTEGER,
    ieee8023MacTransmitteds
        Counter,
    ieee8023MacNotTransmitteds
        Counter,
    ieee8023MacDeferreds
        Counter,
    ieee8023MacCollisions
        Counter,
    ieee8023MacSingleCollisions
        Counter,
    ieee8023MacMultipleCollisions
        Counter,
    ieee8023MacExcessCollisions
        Counter,
    ieee8023MacLateCollisions
        Counter,
    ieee8023MacCarrierLostErrors
        Counter,
    ieee8023MacNoHeartBeatErrors
        Counter,
    ieee8023MacFramesReceiveds
        Counter,
    ieee8023MacUndeliverableFramesReceiveds
        Counter,
    ieee8023MacCrcErrors
        Counter,
    ieee8023MacAlignmentErrors
        Counter,
    ieee8023MacResourceErrors
        Counter,
    ieee8023MacControlFieldErrors
        Counter,
    ieee8023MacUnknownProtocolErrors
        Counter,
    ieee8023MacMulticastsAccepteds
        Counter,
    ieee8023MacMulticastsAccepteds
        Counter,
    ieee8023MacInfiniteDeferrals
        Counter,
    ieee8023MacUnderflowErrors
        Counter,
    ieee8023MacNoResources
        Counter,
    ieee8023MacLengthErrors
        Counter
}

ieee8023MacIndex OBJECT-TYPE
    SYNTAX  INTEGER
    ACCESS  read-only
    STATUS  mandatory
    DESCRIPTION
        "The index value which uniquely identifies the interface/port to
         which this entry is applicable.  The interface/port identified by
         a particular value of this index is the same interface/port as
         identified by the same value of ifIndex."
    ::= { ieee8023MacEntry 1 }

ieee8023MacTransmitteds OBJECT-TYPE
    SYNTAX  Counter
    ACCESS  read-only
    STATUS  mandatory
    DESCRIPTION
        "The number of frames successfully transmitted."
    ::= { ieee8023MacEntry 2 }

ieee8023MacNotTransmitteds OBJECT-TYPE
    SYNTAX  Counter
    ACCESS  read-only
    STATUS  mandatory
    DESCRIPTION
        "The number of frames not transmitted."
    ::= { ieee8023MacEntry 3 }

ieee8023MacDeferreds OBJECT-TYPE
    SYNTAX  Counter
    ACCESS  read-only
    STATUS  mandatory
    DESCRIPTION
        "Number of frames which were successfully transmitted after a
         deferral.  If any collisions occurred before transmission,
         xmtDeferredTransmission isn't incremented."
    ::= { ieee8023MacEntry 4 }

ieee8023MacCollisions OBJECT-TYPE
    SYNTAX  Counter
    ACCESS  read-only
    STATUS  mandatory
    DESCRIPTION
        "Total number of transmit attempts that were retransmitted due to
         collisions, and are subsequently transmitted successfully."
    ::= { ieee8023MacEntry 5 }

ieee8023MacSingleCollisions OBJECT-TYPE
    SYNTAX  Counter
    ACCESS  read-only
    STATUS  mandatory
    DESCRIPTION
        "Number of transmit attempts that are involved in a single
         collision, and are subsequently transmitted successfully."
    ::= { ieee8023MacEntry 6 }

ieee8023MacMultipleCollisions OBJECT-TYPE
    SYNTAX  Counter
    ACCESS  read-only
    STATUS  mandatory
    DESCRIPTION
        "Number of transmit attempts that are involved in between one and
         fifteen collision attempts, and are subsequently transmitted
         successfully."
    ::= { ieee8023MacEntry 7 }

ieee8023MacExcessCollisions OBJECT-TYPE
    SYNTAX  Counter
    ACCESS  read-only
    STATUS  mandatory
    DESCRIPTION
        "The number of transmits that occur after more than 15 collisions,
         and are subsequently transmitted successfully."
    ::= { ieee8023MacEntry 8 }

ieee8023MacLateCollisions OBJECT-TYPE
    SYNTAX  Counter
    ACCESS  read-only
    STATUS  mandatory
    DESCRIPTION
        "The number of collisions that occured after one end-to-end frame
         propagation delay."
    ::= { ieee8023MacEntry 9 }

ieee8023MacCarrierLostErrors OBJECT-TYPE
    SYNTAX  Counter
    ACCESS  read-only
    STATUS  mandatory
    DESCRIPTION
        "Number of times that carrier sense was lost when attempting to
         transmit."
    ::= { ieee8023MacEntry 10 }

ieee8023MacNoHeartBeatErrors OBJECT-TYPE
    SYNTAX  Counter
    ACCESS  read-only
    STATUS  mandatory
    DESCRIPTION
        "The number of times the MAU failed to assert SQE after
         transmitting a packet."
    ::= { ieee8023MacEntry 11 }

ieee8023MacFramesReceiveds OBJECT-TYPE
    SYNTAX  Counter
    ACCESS  read-only
    STATUS  mandatory
    DESCRIPTION
        "The number of frames successfully received."
    ::= { ieee8023MacEntry 12 }

ieee8023MacUndeliverableFramesReceiveds OBJECT-TYPE
    SYNTAX  Counter
    ACCESS  read-only
    STATUS  mandatory
    DESCRIPTION
        "The number of frames received that could not be delivered because
         the software buffer was overrun when frames were sent faster than
         they could be received."
    ::= { ieee8023MacEntry 13 }

ieee8023MacCrcErrors OBJECT-TYPE
    SYNTAX  Counter
    ACCESS  read-only
    STATUS  mandatory
    DESCRIPTION
        "The number of Cyclical Redundancy Check (CRC) errors detected."
    ::= { ieee8023MacEntry 14 }

ieee8023MacAlignmentErrors OBJECT-TYPE
    SYNTAX  Counter
    ACCESS  read-only
    STATUS  mandatory
    DESCRIPTION
        "The number of frames received that were both misaligned and had
         bad CRC."
    ::= { ieee8023MacEntry 15 }

ieee8023MacResourceErrors OBJECT-TYPE
    SYNTAX  Counter
    ACCESS  read-only
    STATUS  mandatory
    DESCRIPTION
        "The number of frames received that were lost due to lack of
         resources."
    ::= { ieee8023MacEntry 16 }

ieee8023MacControlFieldErrors OBJECT-TYPE
    SYNTAX  Counter
    ACCESS  read-only
    STATUS  mandatory
    DESCRIPTION
        "The number of frames received with errors in the control field."
    ::= { ieee8023MacEntry 17 }

ieee8023MacUnknownProtocolErrors OBJECT-TYPE
    SYNTAX  Counter
    ACCESS  read-only
    STATUS  mandatory
    DESCRIPTION
        "The number frames dropped because the type field or sap field
         referenced an invalid protocol."
    ::= { ieee8023MacEntry 18 }

ieee8023MacMulticastsAccepteds OBJECT-TYPE
    SYNTAX  Counter
    ACCESS  read-only
    STATUS  mandatory
    DESCRIPTION
        "Number of accepted muliticast addresses."
    ::= { ieee8023MacEntry 19 }

ieee8023MacInfiniteDeferrals OBJECT-TYPE
    SYNTAX  Counter
    ACCESS  read-only
    STATUS  mandatory
    DESCRIPTION
        "The number of frames not transmitted successfully
         due to excessive number of deferrals."
    ::= { ieee8023MacEntry 20 }

ieee8023MacUnderflowErrors OBJECT-TYPE
    SYNTAX  Counter
    ACCESS  read-only
    STATUS  mandatory
    DESCRIPTION
        "The number of frames not transmitted successfully
         because an underflow occurred on the transmit."
    ::= { ieee8023MacEntry 21 }

ieee8023MacNoResources OBJECT-TYPE
    SYNTAX  Counter
    ACCESS  read-only
    STATUS  mandatory
    DESCRIPTION
        "The number of frames not transmitted successfully
         because the MAC lacked resources to handle the frame."
    ::= { ieee8023MacEntry 22 }

ieee8023MacLengthErrors OBJECT-TYPE
    SYNTAX  Counter
    ACCESS  read-only
    STATUS  mandatory
    DESCRIPTION
        "The number of frames received that have length errors."
    ::= { ieee8023MacEntry 23 }


--  The 802.3 Multicast Address Table

ieee8023MacMcaTable OBJECT-TYPE
    SYNTAX  SEQUENCE OF Ieee8023MacMcaTableEntry
    ACCESS  not-accessible
    STATUS  optional
    DESCRIPTION
        "The 802.3 multicast address table."
    ::= { ieee8023Mac 2 }

ieee8023MacMcaTableEntry OBJECT-TYPE
    SYNTAX  Ieee8023MacMcaTableEntry
    ACCESS  not-accessible
    STATUS  optional
    DESCRIPTION
        "Entries in the ieee8023MacMcaTable."
    ::= { ieee8023MacMcaTable 1 }

Ieee8023MacMcaTableEntry ::=
    SEQUENCE {
        ieee8023MacMcaIndex
            INTEGER,
        ieee8023MacMcaAddress
            OCTET STRING
    }

ieee8023MacMcaIndex OBJECT-TYPE
    SYNTAX  INTEGER
    ACCESS  read-only
    STATUS  optional
    DESCRIPTION
        "The index corresponding to a particular instance
         in the ieee8023MacMcaTable."
    ::= { ieee8023MacMcaTableEntry 1 }

ieee8023MacMcaAddress OBJECT-TYPE
    SYNTAX  OCTET STRING
    ACCESS  read-only
    STATUS  optional
    DESCRIPTION
        "The multicast address of a particular instance in
         the ieee8023McaTable."
    ::= { ieee8023MacMcaTableEntry 2 }


--  Other 802.3 Objects

ieee8023MacState OBJECT-TYPE
    SYNTAX  INTEGER {
                offline(1),
                initializing(2),
                online(4),
                error(5),
                io-not-ready(6)
            }
    ACCESS  read-only
    STATUS  optional
    DESCRIPTION
        "A state variable that indicates the current state of the MAC
         driver."
    ::= { ieee8023Mac 3 }

ieee8023MacConfigurationStatus OBJECT-TYPE
    SYNTAX  INTEGER {
                internal-mau-selected1(1),
                internal-mau-selected5(5),
                internal-mau-selected13(13),
                external-mau-selected(14)
            }
    ACCESS  read-only
    STATUS  optional
    DESCRIPTION
        "These are the four bits of hardware power sense and
         jumper sense registers:

            15  14  13  12  11
            +---+---+---+---+----------+
            |apa|mpa|ext|int|  unused  |
            +---+---+---+---+----------+

            unused    Reserved for future status.
            apa       12v power detected at the AUI connector.
            mpa       12v power detected at the Peripheral
            interface.
            ext       External AUI connector selected.
            int       Internal tranceiver selected."
    ::= { ieee8023Mac 4 }

ieee8023MacNumberActiveMCAs OBJECT-TYPE
    SYNTAX  INTEGER
    ACCESS  read-only
    STATUS  optional
    DESCRIPTION
        "The number of entries in the multicast address table."
    ::= { ieee8023Mac 5 }


-- The HP Network Peripheral Card (npCard) Group
-- The System subgroup of npCard

npSysState OBJECT-TYPE
    SYNTAX  INTEGER {
                offline(1),
                initializing(2),
                online(4),
                error(5),
                io-not-ready(6)
            }
    ACCESS  read-only
    STATUS  optional
    DESCRIPTION
        "The state of the LAN card to network peripheral
         interface driver."
    ::={ npSys 1 }

npSysStatusMessage OBJECT-TYPE
    SYNTAX  DisplayString (SIZE (0..255))
    ACCESS  read-only
    STATUS  optional
    DESCRIPTION
        "A status string reflecting the current state of the card
         and peripheral."
    ::={ npSys 2 }

npSysPeripheralFatalError OBJECT-TYPE
    SYNTAX  INTEGER (0..255)
    ACCESS  read-only
    STATUS  optional
    DESCRIPTION
        "The most recent peripheral fatal error that is
         being displayed on the peripheral's display panel.
         The error typically appears as a '80 Service
         (00xx)' error.  Refer to peripheral documentation
         to determine what the error means."
    ::={ npSys 3 }

npSysCardFatalError OBJECT-TYPE
    SYNTAX  INTEGER (0..255)
    ACCESS  read-only
    STATUS  optional
    DESCRIPTION
        "The most recent LAN Card error that is being
         displayed on the peripheral's display panel.  The
         error typically appears as a '80 Service (01xx)'
         error.  Refer to peripheral documentation to
         determine what the error means."
    ::={ npSys 4 }

npSysMaximumWriteBuffers OBJECT-TYPE
    SYNTAX  INTEGER
    ACCESS  read-only
    STATUS  optional
    DESCRIPTION
        "The maximum number of write buffers configured for
         the LAN card (this translates to the write window
         size of the connection)."
    ::={ npSys 5 }

npSysMaximumReadBuffers OBJECT-TYPE
    SYNTAX  INTEGER
    ACCESS  read-only
    STATUS  optional
    DESCRIPTION
        "The maximum number of read buffers configured for
         the LAN card (this translates to the read window
         size of the connection)."
    ::={ npSys 6 }

npSysTotalBytesRecvs OBJECT-TYPE
    SYNTAX  Counter
    ACCESS  read-only
    STATUS  optional
    DESCRIPTION
        "The total number of bytes received since reset."
    ::={ npSys 7 }

npSysTotalBytesSents OBJECT-TYPE
    SYNTAX  Counter
    ACCESS  read-only
    STATUS  optional
    DESCRIPTION
        "The total number of bytes sent since reset."
    ::={ npSys 8 }

npSysCurrReadReq OBJECT-TYPE
    SYNTAX  Gauge
    ACCESS  read-only
    STATUS  optional
    DESCRIPTION
        "The current number of read data buffers owned by
         the LAN card."
    ::={ npSys 9 }

-- The following 2 objects are from the original Lan Manager MIB.  They
-- need to exist to be backward compatible.

npCardPFatalErr OBJECT-TYPE
    SYNTAX  INTEGER (0..255)
    ACCESS  read-only
    STATUS  optional
    DESCRIPTION
        "The most recent peripheral fatal error that is
         being displayed on the peripheral's display panel.
         The error typically appears as a '80 Service
         (00xx)' error.  Refer to peripheral documentation
         to determine what the error means."
    ::={ npCard 2 }

npCardIoFatalErr OBJECT-TYPE
    SYNTAX  INTEGER (0..255)
    ACCESS  read-only
    STATUS  optional
    DESCRIPTION
        "The most recent LAN Card error that is being
         displayed on the peripheral's display panel.  The
         error typically appears as a '80 Service (01xx)'
         error.  Refer to peripheral documentation to
         determine what the error means."
    ::={ npCard 3 }

--- The Card Connection Statistics subgroup of npCard

npConnsAccepts OBJECT-TYPE
    SYNTAX  Counter
    ACCESS  read-only
    STATUS  optional
    DESCRIPTION
        "The number of connections accepted since reset."
    ::={ npConns 1 }

npConnsRefuseds OBJECT-TYPE
    SYNTAX  Counter
    ACCESS  read-only
    STATUS  optional
    DESCRIPTION
        "The number of connections refused since reset.  Connections
         are refused for the following reasons: a connection is already
         active, the peripheral is offline, the network peripheral
         interface is not ready for connections after a power-up or
         reset, or there isn't enough buffer space on the card to
         establish a connection."
    ::={ npConns 2 }

npConnsDenys OBJECT-TYPE
    SYNTAX  Counter
    ACCESS  read-only
    STATUS  optional
    DESCRIPTION
        "The number of connections that the card denied due to failure
         to match the access list."
    ::={ npConns 3 }

npConnsDenysIP OBJECT-TYPE
    SYNTAX  IpAddress
    ACCESS  read-only
    STATUS  optional
    DESCRIPTION
        "The IP address of the last node to be denied a connection
         due to failure to match the access list."
    ::={ npConns 4 }

npConnsAborts OBJECT-TYPE
    SYNTAX  Counter
    ACCESS  read-only
    STATUS  optional
    DESCRIPTION
        "The number of connections aborted due to a network problem."
    ::={ npConns 5 }

npConnsAbortReason OBJECT-TYPE
    SYNTAX  DisplayString (SIZE (0..255))
    ACCESS  read-only
    STATUS  optional
    DESCRIPTION
        "The textual description of why the last abort on the
         card occurred."
    ::={ npConns 6 }

npConnsAbortIP OBJECT-TYPE
    SYNTAX  IpAddress
    ACCESS  read-only
    STATUS  optional
    DESCRIPTION
        "The IP address of the last node to establish a connection
         before the card aborted."
    ::={ npConns 7 }

npConnsAbortPort OBJECT-TYPE
    SYNTAX  INTEGER (0..65535)
    ACCESS  read-only
    STATUS  optional
    DESCRIPTION
        "The port of the last node to establish a connection
         before the card aborted."
    ::={ npConns 8 }

npConnsAbortTime OBJECT-TYPE
    SYNTAX  TimeTicks
    ACCESS  read-only
    STATUS  optional
    DESCRIPTION
        "The time (in hundredths of a second) since the last
         time the card was aborted."
    ::={ npConns 9 }

npConnsState OBJECT-TYPE
    SYNTAX  INTEGER {
                up(1),
                down(2)
            }
    ACCESS  read-only
    STATUS  optional
    DESCRIPTION
        "State of current connection to card."
    ::={ npConns 10 }

npConnsIP OBJECT-TYPE
    SYNTAX  IpAddress
    ACCESS  read-only
    STATUS  optional
    DESCRIPTION
        "Remote IP address of the node currently connected to the card.
         Zero if no connection is active."
    ::={ npConns 11 }

npConnsPort OBJECT-TYPE
    SYNTAX  INTEGER (0..65535)
    ACCESS  read-only
    STATUS  optional
    DESCRIPTION
        "Remote port number of the node currently connected to the card.
         Zero if no connection is active."
    ::={ npConns 12 }

npConnsPeriphClose OBJECT-TYPE
    SYNTAX  INTEGER
    ACCESS  read-only
    STATUS  optional
    DESCRIPTION
        "The number of connections closed in response to a peripheral
         request I/O channel reset request."
    ::={ npConns 13 }

npConnsIdleTimeouts OBJECT-TYPE
    SYNTAX  INTEGER
    ACCESS  read-only
    STATUS  optional
    DESCRIPTION
        "The number of connections closed due to an idle timeout."
    ::={ npConns 14 }

npConnsNmClose OBJECT-TYPE
    SYNTAX  INTEGER
    ACCESS  read-only
    STATUS  optional
    DESCRIPTION
        "The number of connections closed by SetRequests to the MIB
         variable, npCtlCloseConnection."
    ::={ npConns 15 }

npConnsBytesRecvds OBJECT-TYPE
    SYNTAX  Counter
    ACCESS  read-only
    STATUS  optional
    DESCRIPTION
        "The number of bytes received by this connection."
    ::={ npConns 16 }

npConnsBytesSents OBJECT-TYPE
    SYNTAX  Counter
    ACCESS  read-only
    STATUS  optional
    DESCRIPTION
        "The number of bytes transmitted by this connection."
    ::={ npConns 17 }


--- The Card Configuration subgroup of npCard

npCfgSource OBJECT-TYPE
--  SYNTAX  INTEGER
    SYNTAX  INTEGER {		-- RAL mod
                bootp(0),	-- RAL mod
                manual(1),	-- RAL mod
                other(2),	-- RAL mod
                manual(3),	-- RAL mod
                bootp(4),	-- RAL mod
                dhcp(5)		-- RAL mod
            }			-- RAL mod
--              BOOTP(0),
--              FRONTPANEL(1)
    ACCESS  read-only
    STATUS  optional
    DESCRIPTION
        "This indicates whether the card obtained its configuration
         from the system that sent the BOOTP reply or from the
         front panel."
    ::={ npCfg 1 }

npCfgYiaddr OBJECT-TYPE
    SYNTAX  IpAddress
    ACCESS  read-only
    STATUS  optional
    DESCRIPTION
        "The IP address assigned to the card from the BOOTP reply
         yiaddr field."
    ::={ npCfg 2 }

npCfgSiaddr OBJECT-TYPE
    SYNTAX  IpAddress
    ACCESS  read-only
    STATUS  optional
    DESCRIPTION
        "The IP address of the TFTP server from the BOOTP reply
         siaddr field."
    ::={ npCfg 3 }

npCfgGiaddr OBJECT-TYPE
    SYNTAX  IpAddress
    ACCESS  read-only
    STATUS  optional
    DESCRIPTION
        "The IP address of the TFTP gateway from the BOOTP reply
         giaddr field."
    ::={ npCfg 4 }

npCfgLogServer OBJECT-TYPE
    SYNTAX  IpAddress
    ACCESS  read-only
    STATUS  optional
    DESCRIPTION
        "The IP address of the Log Server from the BOOTP reply
         Tag: 7 field."
    ::={ npCfg 5 }

npCfgSyslogFacility OBJECT-TYPE
    SYNTAX  INTEGER
    ACCESS  read-only
    STATUS  optional
    DESCRIPTION
        "This specifies the facility identifier used in syslog messages
         generated by the card."
    ::={ npCfg 6 }

npCfgAccessState OBJECT-TYPE
    SYNTAX  INTEGER {
                allowed(1),
                not-allowed(2)
            }
    ACCESS  read-only
    STATUS  optional
    DESCRIPTION
        "An indication of whether or not the requesting host
         is allowed to connect to the card as dictated by the
         access list."
    ::={ npCfg 7 }

npCfgAccessListNum OBJECT-TYPE
    SYNTAX  INTEGER
    ACCESS  read-only
    STATUS  optional
    DESCRIPTION
        "The number of access list entries."
    ::={ npCfg 8 }

npCfgAccessListTable OBJECT-TYPE
    SYNTAX  SEQUENCE OF AccessListEntry
    ACCESS  not-accessible
    STATUS  optional
    DESCRIPTION
        "List of access addresses and masks."
    ::={ npCfg 9 }

accessListEntry OBJECT-TYPE
    SYNTAX  AccessListEntry
    ACCESS  not-accessible
    STATUS  optional
    DESCRIPTION
        "Each entry contains an access address and mask."
    INDEX    { npCfgAccessListIndex }
    ::={ npCfgAccessListTable 1 }

AccessListEntry ::=
    SEQUENCE {
        npCfgAccessListIndex
            INTEGER,
        npCfgAccessListAddress
            IpAddress,
        npCfgAccessListAddrMask
            IpAddress
    }

npCfgAccessListIndex OBJECT-TYPE
    SYNTAX  INTEGER (0..9)
    ACCESS  read-only
    STATUS  optional
    DESCRIPTION
        "Index to the configuration access list table."
    ::={ accessListEntry 1 }

npCfgAccessListAddress OBJECT-TYPE
    SYNTAX  IpAddress
    ACCESS  read-only
    STATUS  optional
    DESCRIPTION
        "Address to compare with after applying the wildcard to
         the requestor's address."
    ::={ accessListEntry 2 }

npCfgAccessListAddrMask OBJECT-TYPE
    SYNTAX  IpAddress
    ACCESS  read-only
    STATUS  optional
    DESCRIPTION
        "Address mask used to help determine whether or not a given
         IP address is allowed access to the card.  An IP address is
         allowed access if (Addr & AddrMask) == (IP & AddrMask)."
    ::={ accessListEntry 3 }

npCfgIdleTimeout OBJECT-TYPE
    SYNTAX  INTEGER
    ACCESS  read-only
    STATUS  optional
    DESCRIPTION
        "The idle timeout is the length in seconds after which an
         idle connection is terminated.  A value of zero disables
         the timeout."
    ::={ npCfg 10 }

npCfgLocalSubnets OBJECT-TYPE
    SYNTAX  INTEGER 
--              none(0),
--              exist(1)
    ACCESS  read-only
    STATUS  optional
    DESCRIPTION
        "An indication of whether or not the card recognizes
         any local subnets."
    ::={ npCfg 11 }


-- The TCP subgroup of npCard

npTcpInSegInOrders OBJECT-TYPE
    SYNTAX  Counter
    ACCESS  read-only
    STATUS  optional
    DESCRIPTION
        "The number of TCP segments received in order."
    ::={ npTcp 1 }

npTcpInSegOutOfOrders OBJECT-TYPE
    SYNTAX  Counter
    ACCESS  read-only
    STATUS  optional
    DESCRIPTION
        "The number of TCP segments received out of order."
    ::={ npTcp 2 }

npTcpInSegZeroProbes OBJECT-TYPE
    SYNTAX  Counter
    ACCESS  read-only
    STATUS  optional
    DESCRIPTION
        "The number of TCP zero window probes received."
    ::={ npTcp 3 }

npTcpInDiscards OBJECT-TYPE
    SYNTAX  Counter
    ACCESS  read-only
    STATUS  optional
    DESCRIPTION
        "The number of TCP segments received that were
         discarded."
    ::={ npTcp 4 }


-- The Card Control subgroup of npCard

npCtlReconfigIP OBJECT-TYPE
    SYNTAX  IpAddress
    ACCESS  read-only
    STATUS  optional
    DESCRIPTION
        "The IP address of the last node to request a reconfig
         of the card.  This value is preserved across a reconfig."
    ::={ npCtl 1 }

npCtlReconfigPort OBJECT-TYPE
    SYNTAX  INTEGER (0..65535)
    ACCESS  read-only
    STATUS  optional
    DESCRIPTION
        "The port of the last node to request a reconfig of the
         card.  This value is preserved across a reconfig."
    ::={ npCtl 2 }

npCtlReconfigTime OBJECT-TYPE
    SYNTAX  TimeTicks
    ACCESS  read-only
    STATUS  optional
    DESCRIPTION
        "The time (in hundredths of a second) since the last
         time the card was reconfigured."
    ::={ npCtl 3 }

npCtlCloseIP OBJECT-TYPE
    SYNTAX  IpAddress
    ACCESS  read-only
    STATUS  optional
    DESCRIPTION
        "The IP address of the last node to request a close of
         the peripheral data connection on the card.  This
         value is cleared on a reconfig."
    ::={ npCtl 4 }

npCtlClosePort OBJECT-TYPE
    SYNTAX  INTEGER (0..65535)
    ACCESS  read-only
    STATUS  optional
    DESCRIPTION
        "The port of the last node to request a close of the
         peripheral data connection on the card.  This
         value is cleared on a reconfig."
    ::={ npCtl 5 }

npCtlImageDump OBJECT-TYPE
    SYNTAX  INTEGER 
--              OFF(0),
--              DUMP(1)
    ACCESS  read-write
    STATUS  optional
    DESCRIPTION
        "Writing a one (1) to this variable causes the card to dump
         its RAM image into a file using TFTP.  The file is dumped
         onto the BOOTP server machine whose IP address is in the MIB
         variable, npCfgSiaddr { npCfg 3 }.  The file name is:
         npi.<IPaddr> in the tftp directory, where <IPaddr> is the
         IP address of the card.  The file must be writable by TFTP."
    ::= { npCtl 6 }

npCtlCloseConnection OBJECT-TYPE
    SYNTAX  INTEGER 
--              OFF(0),
--              CLOSE(1)
    ACCESS  read-write
    STATUS  optional
    DESCRIPTION
        "Writing a one (1) to this variable causes the card to close
         the current peripheral data connection"
    ::= { npCtl 7 }

npCtlReconfig OBJECT-TYPE
    SYNTAX  INTEGER 
--              OFF(0),
--              REBOOT(1)
    ACCESS  read-write
    STATUS  optional
    DESCRIPTION
        "Writing a one (1) to this variable causes the card to
         reconfigure itself by doing the BOOTP/TFTP configuration
         activity."
    ::= { npCtl 8 }

npCtlProtocolSet OBJECT-TYPE
    SYNTAX  INTEGER 
    ACCESS  read-write
    STATUS  optional
    DESCRIPTION
        "Reading this 4 byte integer will show several things.  It will
         show.  Writing the protocol bits will enable/disable the protocols
         specified."
    ::={ npCtl 9 }


-- The HP Modular Input/Output (MIO) subgroup of npCard
-- The Card Status Entry

npNpiCardStatusEntry OBJECT-TYPE
    SYNTAX  SEQUENCE OF NpNpiCardStatusEntry
    ACCESS  not-accessible
    STATUS  optional
    DESCRIPTION
        "These are the set of status bytes that the
         peripheral passes to the network card.  The
         peripheral and LAN card exchange these status
         bytes whenever an event causes the status to
         change."
    ::={ npNpi 1 }

NpNpiCardStatusEntry ::=
    SEQUENCE {
        npNpiCseDataState
            INTEGER,
        npNpiCseErrorCode
            INTEGER,
        npNpiCseLinkEvent
            INTEGER,
        npNpiCseReadMode
            INTEGER,
        npNpiCseWriteMode
            INTEGER,
        npNpiCseWarningCode
            INTEGER,
        npNpiCseConnectionState
            INTEGER,
        npNpiCseNovWarningCode
            INTEGER,
        npNpiCseLlcWarningCode
            INTEGER,
        npNpiCseTcpWarningCode
            INTEGER,
        npNpiCseAtkWarningCode
            INTEGER
}

npNpiCseDataState OBJECT-TYPE
    SYNTAX  INTEGER (0..255)
    ACCESS  read-only
    STATUS  optional
    DESCRIPTION
        "The data state of the LAN card."
    ::={ npNpiCardStatusEntry 1 }

npNpiCseErrorCode OBJECT-TYPE
    SYNTAX  INTEGER (0..255)
    ACCESS  read-only
    STATUS  optional
    DESCRIPTION
        "The LAN card's error code."
    ::={ npNpiCardStatusEntry 2 }

npNpiCseLinkEvent OBJECT-TYPE
    SYNTAX  INTEGER (0..255)
    ACCESS  read-only
    STATUS  optional
    DESCRIPTION
        "The LAN link event (reset or initialized or
         triggered)."
    ::={ npNpiCardStatusEntry 3 }

npNpiCseReadMode OBJECT-TYPE
    SYNTAX  INTEGER (0..255)
    ACCESS  read-only
    STATUS  optional
    DESCRIPTION
        "The state of the LAN card's read channel (operate
         or idle)."
    ::={ npNpiCardStatusEntry 4 }

npNpiCseWriteMode OBJECT-TYPE
    SYNTAX  INTEGER (0..255)
    ACCESS  read-only
    STATUS  optional
    DESCRIPTION
        "The state of the LAN card's write channel (operate
         or idle)."
    ::={ npNpiCardStatusEntry 5 }

npNpiCseWarningCode OBJECT-TYPE
    SYNTAX  INTEGER (0..255)
    ACCESS  read-only
    STATUS  optional
    DESCRIPTION
        "This indicates that the LAN card channel zero
         has encountered an error condition which isn't 
         serious enough to shut the peripheral down, 
         but should be checked out."
    ::={ npNpiCardStatusEntry 6 }

npNpiCseConnectionState OBJECT-TYPE
    SYNTAX  INTEGER (0..255)
    ACCESS  read-only
    STATUS  optional
    DESCRIPTION
        "Indicates whether or not the peripheral is
         currently connected to a server."
    ::={ npNpiCardStatusEntry 7 }

npNpiCseNovWarningCode OBJECT-TYPE
    SYNTAX  INTEGER (0..255)
    ACCESS  read-only
    STATUS  optional
    DESCRIPTION
        "This indicates that the Novell stack has encountered
         an error condition which isn't serious enough to
         shut the peripheral down, but should be checked
         out."
    ::={ npNpiCardStatusEntry 8 }

npNpiCseLlcWarningCode OBJECT-TYPE
    SYNTAX  INTEGER (0..255)
    ACCESS  read-only
    STATUS  optional
    DESCRIPTION
        "This indicates that the LLC stack has encountered
         an error condition which isn't serious enough to
         shut the peripheral down, but should be checked
         out."
    ::={ npNpiCardStatusEntry 9 }

npNpiCseTcpWarningCode OBJECT-TYPE
    SYNTAX  INTEGER (0..255)
    ACCESS  read-only
    STATUS  optional
    DESCRIPTION
        "This indicates that the TCP stack has encountered
         an error condition which isn't serious enough to
         shut the peripheral down, but should be checked
         out."
    ::={ npNpiCardStatusEntry 10 }

npNpiCseAtkWarningCode OBJECT-TYPE
    SYNTAX  INTEGER (0..255)
    ACCESS  read-only
    STATUS  optional
    DESCRIPTION
        "This indicates that the AppleTalk stack has encountered
         an error condition which isn't serious enough to
         shut the peripheral down, but should be checked
         out."
    ::={ npNpiCardStatusEntry 11 }

--  The Peripheral Attribute Entry

npNpiPeripheralAttributeCount OBJECT-TYPE
    SYNTAX  INTEGER (0..32)
    ACCESS  read-only
    STATUS  optional
    DESCRIPTION
        "The number of valid bytes of peripheral attributes
         received from the peripheral."
    ::={ npNpi 2 }

npNpiPeripheralAttributeEntry OBJECT-TYPE
    SYNTAX  NpNpiPeripheralAttributeEntry
    ACCESS  not-accessible
    STATUS  optional
    DESCRIPTION
        "The set of bytes that describe the peripheral's
         attributes as received from the peripheral during
         the setup of the peripheral to LAN card
         communications."
    ::={ npNpi 3 }

NpNpiPeripheralAttributeEntry ::=
    SEQUENCE {
        npNpiPaeLinkDirection
            INTEGER,
        npNpiPaeClass
            INTEGER,
        npNpiPaeIdentification
            INTEGER,
        npNpiPaeRevision
            INTEGER,
        npNpiPaeAppleTalk
            INTEGER,
        npNpiPaeMessage
            INTEGER,
        npNpiPaeReserved 
            INTEGER,
        npNpiPaeMultichanFlag
            INTEGER,
        npNpiPaePad
            OCTET STRING
}

npNpiPaeLinkDirection OBJECT-TYPE
    SYNTAX  INTEGER 
--              NO-PERIPH-DATA-XFER(0),
--              XFER-PERIPH-TO-HOST(1),
--              XFER-HOST-TO-PERIPH(2),
--              BI-DIRECT-PERIPH-DATA-XFER(3)
    ACCESS  read-only
    STATUS  optional
    DESCRIPTION
        "The directions that the peripheral is able to
         transfer data (read and write channels, read
         channel only, or write channel only)."
    ::={ npNpiPeripheralAttributeEntry 1 }

npNpiPaeClass OBJECT-TYPE
    SYNTAX  INTEGER 
--              UNDEFINED-CLASS(0),
--              PRINTER(1),
--              PLOTTER(2),
--              INSTRUMENT(3)
    ACCESS  read-only
    STATUS  optional
    DESCRIPTION
        "The class assigned to the peripheral onto which
         this card is plugged."
    ::={ npNpiPeripheralAttributeEntry 2 }

npNpiPaeIdentification OBJECT-TYPE
    SYNTAX  INTEGER 
--              UNDEFINED-PERIPH(0),
--              LASERJET-IIISI(1),
--              LASERJET-4SI(5)
    ACCESS  read-only
    STATUS  optional
    DESCRIPTION
        "The Identification number of the peripheral.  These values are
         defined in the MIO spec.  DesignJet, PaintJet XL300, and 
         DesignJet/600 peripherals will identify themselves as 
         LaserJet-IIIsi."
    ::={ npNpiPeripheralAttributeEntry 3 }

npNpiPaeRevision OBJECT-TYPE
    SYNTAX  INTEGER (0..255)
    ACCESS  read-only
    STATUS  optional
    DESCRIPTION
        "The revision number of the peripheral."
    ::={ npNpiPeripheralAttributeEntry 4 }

npNpiPaeAppleTalk OBJECT-TYPE
    SYNTAX  INTEGER
--              NO-APPLETALK-SUPPORT(0),
--              APPLETALK-SUPPORT(1)
    ACCESS  read-only
    STATUS  optional
    DESCRIPTION
        "Indicates the peripheral supports functionality
         that the apple talk protocol network provides."
    ::={ npNpiPeripheralAttributeEntry 5 }

npNpiPaeMessage OBJECT-TYPE
    SYNTAX  INTEGER 
--              NO-MSGMODE-SUPPORT(0),
--              MSGMODE-SUPPORT(1)
    ACCESS  read-only
    STATUS  optional
    DESCRIPTION
        "Reserved for future use."
    ::={ npNpiPeripheralAttributeEntry 6 }

npNpiPaeReserved OBJECT-TYPE
    SYNTAX  INTEGER 
    ACCESS  read-only
    STATUS  optional
    DESCRIPTION
        "This field is an unused byte."
    ::={ npNpiPeripheralAttributeEntry 7 }

npNpiPaeMultichanFlag OBJECT-TYPE
    SYNTAX  INTEGER 
    ACCESS  read-only
    STATUS  optional
    DESCRIPTION
        "An indication of how many MIO channels the peripheral supports."
    ::={ npNpiPeripheralAttributeEntry 8 }

npNpiPaePad OBJECT-TYPE
    SYNTAX  OCTET STRING 
    ACCESS  read-only
    STATUS  optional
    DESCRIPTION
        "This object is a pad for future use."
    ::={ npNpiPeripheralAttributeEntry 9 }



--  The Card Attribute Entry

npNpiCardAttributeEntry OBJECT-TYPE
    SYNTAX  NpNpiCardAttributeEntry 
    ACCESS  not-accessible
    STATUS  optional
    DESCRIPTION
        "The set of bytes describing the card's attributes
         as stored in the ROM of this particular LAN card."
    ::={ npNpi 4 }

NpNpiCardAttributeEntry ::=
    SEQUENCE {
        npNpiCaeLinkDirection
            INTEGER,
        npNpiCaeClass
            INTEGER,
        npNpiCaeIdentification
            INTEGER,
        npNpiCaeRevision
            INTEGER,
        npNpiCaeAppleTalk
            INTEGER,
        npNpiCaeMessage
            INTEGER,
        npNpiCaeReserved
            INTEGER,
        npNpiCaeMultichan
            INTEGER
}

npNpiCaeLinkDirection OBJECT-TYPE
    SYNTAX  INTEGER 
--              NO-LINK-DATA-XFER(0),
--              XFER-LINK-TO-HOST(1),
--              XFER-HOST-TO-LINK(2),
--              BI-DIRECT-LINK-DATA-XFER(3)
    ACCESS  read-only
    STATUS  optional
    DESCRIPTION
        "The directions that this particular network
         peripheral card is able to transfer data (read and
         write, read only or write only)."
    ::={ npNpiCardAttributeEntry 1 }

npNpiCaeClass OBJECT-TYPE
    SYNTAX  INTEGER 
--              UNDEFINED-CLASS(0),
--              RS-232(1),
--              CENTRONICS(2),
--              CSMA-CD-NETWORK(3),
--              TOKEN-RING-NETWORK(4),
--              SCSI(5),
--              HPIB(6),
--              LOCALTALK(7)
    ACCESS  read-only
    STATUS  optional
    DESCRIPTION
        "The class of this network peripheral card."
    ::={ npNpiCardAttributeEntry 2 }

npNpiCaeIdentification OBJECT-TYPE
    SYNTAX  INTEGER (0..65535)
    ACCESS  read-only
    STATUS  optional
    DESCRIPTION
        "The identification number assigned this network
         peripheral card."
    ::={ npNpiCardAttributeEntry 3 }

npNpiCaeRevision OBJECT-TYPE
    SYNTAX  INTEGER (0..255)
    ACCESS  read-only
    STATUS  optional
    DESCRIPTION
        "The revision number of the network peripheral
         connection card code on this card."
    ::={ npNpiCardAttributeEntry 4 }

npNpiCaeAppleTalk OBJECT-TYPE
    SYNTAX  INTEGER 
--              NO-APPLETALK-SUPPORT(0),
--              APPLETALK-SUPPORT(1)
    ACCESS  read-only
    STATUS  optional
    DESCRIPTION
        "Indicates that the card supports the apple talk
         protocol network."
    ::={ npNpiCardAttributeEntry 5 }

npNpiCaeMessage OBJECT-TYPE
    SYNTAX  INTEGER 
--              NO-MSGMODE-SUPPORT(0),
--              MSGMODE-SUPPORT(1)
    ACCESS  read-only
    STATUS  optional
    DESCRIPTION
        "Indicates that the card supports the messaging mode protocol."
    ::={ npNpiCardAttributeEntry 6 }

npNpiCaeReserved OBJECT-TYPE
    SYNTAX  INTEGER 
    ACCESS  read-only
    STATUS  optional
    DESCRIPTION
        "Reserved object for future use."
    ::={ npNpiCardAttributeEntry 7 }

npNpiCaeMultichan OBJECT-TYPE
    SYNTAX  INTEGER 
    ACCESS  read-only
    STATUS  optional
    DESCRIPTION
        "An indication of how many MIO channels the I/O card supports."
    ::={ npNpiCardAttributeEntry 8 }

--  The Error Log Table subgroup of npCard

npEltErrorLogTable OBJECT-TYPE
    SYNTAX  SEQUENCE OF NpEltEntry
    ACCESS  not-accessible
    STATUS  optional
    DESCRIPTION
        "The LAN card's error log."
    ::={ npElt 1 }

npEltEntry OBJECT-TYPE
    SYNTAX  NpEltEntry
    ACCESS  not-accessible
    STATUS  optional
    DESCRIPTION
        "The LAN card's error log table entries."
    ::={ npEltErrorLogTable 1 }

NpEltEntry ::=
    SEQUENCE {
        npEltErrIndex
            INTEGER,
        npEltErrErrorId
            INTEGER,
        npEltErrErrorParam
            INTEGER,
        npEltErrTimeStamp
            TimeTicks
    }

npEltErrIndex OBJECT-TYPE
    SYNTAX  INTEGER (0..255)
    ACCESS  read-only
    STATUS  optional
    DESCRIPTION
        "The index that uniquely identifies an error log
         entry."
    ::={ npEltEntry 1 }

npEltErrErrorId OBJECT-TYPE
    SYNTAX  INTEGER (0..65535)
    ACCESS  read-only
    STATUS  optional
    DESCRIPTION
        "Identification for this error."
    ::={ npEltEntry 2 }

npEltErrErrorParam OBJECT-TYPE
    SYNTAX  INTEGER (0..4294967295)
    ACCESS  read-only
    STATUS  optional
    DESCRIPTION
        "Error Parameter value."
    ::={ npEltEntry 3 }

npEltErrTimeStamp OBJECT-TYPE
    SYNTAX  TimeTicks
    ACCESS  read-only
    STATUS  optional
    DESCRIPTION
        "Time in timer ticks when error log entry was made."
    ::={ npEltEntry 4 }

--  The IPX group

npIpxGetUnitCfgResp OBJECT-TYPE
    SYNTAX  OCTET STRING
    ACCESS  read-only
    STATUS  optional
    DESCRIPTION
        "This object is the Get Unit Config Response
         structure described in the IPX code.  This
         structure is of variable length depending
         on how many servers are configured."
    ::={ npIpx 1 }

npIpx8022frametype OBJECT-TYPE
    SYNTAX  INTEGER
    ACCESS  read-only
    STATUS  optional
    DESCRIPTION
        "The number of IPX FT8022 frames received."
    ::={ npIpx 2 }

npIpxSNAPframetype OBJECT-TYPE
    SYNTAX  INTEGER
    ACCESS  read-only
    STATUS  optional
    DESCRIPTION
        "The number of IPX FTSNAP frames received."
    ::={ npIpx 3 }

npIpxEthernetframetype OBJECT-TYPE
    SYNTAX  INTEGER
    ACCESS  read-only
    STATUS  optional
    DESCRIPTION
        "The number of IPX FTEthernet frames received."
    ::={ npIpx 4 }

npIpx8023Rawframetype OBJECT-TYPE
    SYNTAX  INTEGER
    ACCESS  read-only
    STATUS  optional
    DESCRIPTION
        "The number of IPX FT8023RAW frames received."
    ::={ npIpx 5 }

npIpxSapInfo OBJECT-TYPE
    SYNTAX  OCTET STRING
    ACCESS  read-only
    STATUS  optional
    DESCRIPTION
        "This is a 50 byte array that contains the following
         information.
           2 bytes:  bindery object type (always 030c in hi-lo order)
          12 bytes:  Mac address of card (ASCII)
           2 bytes:  frame type
                     also high bit (8000) is set if card is not configured
           2 bytes : unit type (hex 81 for NetJet card)
           32 bytes: node name (ASCII) which is:
                     print server name for Queue Server mode
                     printer name for RPTR mode"
    ::={ npIpx 6 }


--  LLC Connection State

llcConnectionstate OBJECT-TYPE
    SYNTAX  INTEGER
    ACCESS  read-only
    STATUS  optional
    DESCRIPTION
        "This is the llc connection state for Lan Manager
         and Lan Server."
    ::={ llcconstategroup 7 }

--- The Trap Group

trapDestinationNum OBJECT-TYPE
    SYNTAX  INTEGER
    ACCESS  read-only
    STATUS  optional
    DESCRIPTION
        "The number of trap destinations."
    ::={ trap 1 }

-- The Trap Destination Table

trapDestinationTable OBJECT-TYPE
    SYNTAX  SEQUENCE OF TrapDestinationEntry
    ACCESS  not-accessible
    STATUS  mandatory
    DESCRIPTION
        "List of addresses to which the agent sends traps."
    ::= { trap 2 }

trapDestinationEntry OBJECT-TYPE
    SYNTAX  TrapDestinationEntry
    ACCESS  not-accessible
    STATUS  mandatory
    DESCRIPTION
        "Each entry contains the address of a management
         station."
    INDEX    { trapDestination }
    ::= { trapDestinationTable 1 }

TrapDestinationEntry ::= SEQUENCE {
    trapDestination
    NetworkAddress
}

trapDestination OBJECT-TYPE
    SYNTAX  NetworkAddress
    ACCESS  read-only
    STATUS  mandatory
    DESCRIPTION
        "Address to which the agent sends traps."
    ::= { trapDestinationEntry 1 }

END
